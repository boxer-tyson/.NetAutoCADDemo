Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit

Public Sub CreateRegion()
    Dim line As AcadLine
    Dim startPoint(0 To 2) As Double, endPoint(0 To 2) As Double
    
    SetPoint3d startPoint, 0, 50, 0
    SetPoint3d endPoint, 0, -50, 0
    Dim mSpace As New clsModelSpace
    Set line = mSpace.AddLine(startPoint, endPoint)
    Dim ents As New clsEntityArray
    ents.Append line
    
    SetPoint3d startPoint, 0, -50, 0
    SetPoint3d endPoint, 100, 0, 0
    Set line = mSpace.AddLine(startPoint, endPoint)
    ents.Append line
    
    SetPoint3d startPoint, 100, 0, 0
    SetPoint3d endPoint, 0, 50, 0
    Set line = mSpace.AddLine(startPoint, endPoint)
    ents.Append line
    
    SetPoint3d startPoint, 0, 50, 0
    SetPoint3d endPoint, -100, 0, 0
    Set line = mSpace.AddLine(startPoint, endPoint)
    ents.Append line
    
    SetPoint3d startPoint, -100, 0, 0
    SetPoint3d endPoint, 0, -50, 0
    Set line = mSpace.AddLine(startPoint, endPoint)
    ents.Append line
    
    Dim regions As Variant
    Dim count As Integer
    If (mSpace.AddRegion(ents.ToArray(), regions, count)) Then
        MsgBox "成功创建" & CStr(count) & "个面域!"
    Else
        MsgBox "创建面域失败!"
    End If
End Sub

Public Sub PrintErrNumber()
    Dim centerPoint(0 To 2) As Double
    SetPoint3d centerPoint, 0, 0, 0
    Dim arc As AcadArc
    Dim mSpace As New clsModelSpace
    Set arc = mSpace.AddArc(centerPoint, 50, 1, 3)
    
    Dim ents(0) As AcadEntity
    Set ents(0) = arc
    
    On Error Resume Next
    
    ThisDrawing.ModelSpace.AddRegion ents
    
    If Err Then
        Debug.Print Err.Number
    End If
End Sub

Public Sub CreatePoly()
'    Dim line As AcadLine
'    Dim startPoint(0 To 2) As Double, endPoint(0 To 2) As Double
'
'    SetPoint3d startPoint, 0, 50, 0
'    SetPoint3d endPoint, 0, -50, 0
'    Dim mSpace As New clsModelSpace
'    Dim ents As New clsEntityArray
'
'    SetPoint3d startPoint, 0, -50, 0
'    SetPoint3d endPoint, 100, 0, 0
'    Set line = mSpace.AddLine(startPoint, endPoint)
'    ents.Append line
'
'    SetPoint3d startPoint, 100, 0, 0
'    SetPoint3d endPoint, 0, 50, 0
'    Set line = mSpace.AddLine(startPoint, endPoint)
'    ents.Append line
'
'    SetPoint3d startPoint, 0, 50, 0
'    SetPoint3d endPoint, -100, 0, 0
'    Set line = mSpace.AddLine(startPoint, endPoint)
'    ents.Append line
'
'    SetPoint3d startPoint, -100, 0, 0
'    SetPoint3d endPoint, 0, -50, 0
'    Set line = mSpace.AddLine(startPoint, endPoint)
'    ents.Append line

    Dim sset As AcadSelectionSet
    Set sset = ThisDrawing.SelectionSets.Add("sset")
    sset.SelectOnScreen
    
    Dim ent As AcadEntity
    Dim ents As New clsEntityArray
    For Each ent In sset
        ents.Append ent
    Next ent
    sset.Delete
    
    Dim poly As AcadLWPolyline
    Dim mSpace As New clsModelSpace
    If (mSpace.AddLWPolylineByEnts(ents.ToArray(), poly)) Then
        MsgBox "成功创建多段线!"
    Else
        MsgBox "创建多段线失败!"
    End If
End Sub

Attribute VB_Name = "cls2dPointArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_verts() As Double             ' 实际保存数据的变量
Private m_bFirstItem As Boolean         ' 当前是否添加的是第一个元素

' 获得点数组中包含的点数
Public Function GetCount() As Integer
    If (m_bFirstItem) Then
        GetCount = 0
    Else
        GetCount = (UBound(m_verts) + 1) / 2
    End If
End Function

' 添加点
Public Function Append(ByVal point As Variant)
    Debug.Assert (VarType(point) = vbArray + vbDouble)
    Debug.Assert (UBound(point) >= 1)
   
    ' 第一个点的空间已经分配，只有后面的点才增加数组的元素个数
    If (m_bFirstItem) Then
        m_bFirstItem = False
    Else
        ReDim Preserve m_verts(UBound(m_verts) + 2)
    End If
    
    ' 为最后一个点赋值
    m_verts(UBound(m_verts) - 1) = point(0)
    m_verts(UBound(m_verts)) = point(1)
End Function

' 删除点
Public Function RemoveAt(ByVal i As Integer) As Boolean
    If (i < 0 Or i > GetCount() - 1) Then
        RemoveAt = False
        Exit Function
    Else
        If (i <> GetCount() - 1) Then
            Dim j As Integer
            For j = i * 2 To UBound(m_verts) - 2
                m_verts(j) = m_verts(j + 2)
            Next j
        End If
        
        If (GetCount() = 1) Then
            m_verts(0) = 0
            m_verts(1) = 0
            m_bFirstItem = True
        Else
            ReDim Preserve m_verts(UBound(m_verts) - 2)
        End If
    End If
End Function

' 插入点
Public Function InsertAt(ByVal i As Integer, ByVal point As Variant) As Boolean
    Debug.Assert (VarType(point) = vbArray + vbDouble)
    Debug.Assert (UBound(point) >= 1)
    
    If (m_bFirstItem) Then
        If (i = 0) Then
            m_verts(0) = point(0)
            m_verts(1) = point(1)
            m_bFirstItem = False
        Else
            InsertAt = False
            Exit Function
        End If
    Else
        If (i < 0 Or i > GetCount()) Then
            InsertAt = False
            Exit Function
        Else
            ReDim Preserve m_verts(UBound(m_verts) + 2)
            
            If (i <> GetCount()) Then
                Dim j As Integer
                For j = UBound(m_verts) To (i + 1) * 2 Step -1
                    m_verts(j) = m_verts(j - 2)
                Next j
            End If
            
            m_verts(i * 2) = point(0)
            m_verts(i * 2 + 1) = point(1)
            
            InsertAt = True
        End If
    End If
End Function

' 删除最后一个点
Public Function RemoveLast() As Boolean
    If (GetCount() > 1) Then
        ReDim Preserve m_verts(UBound(m_verts) - 2)
        RemoveLast = True
    ElseIf (GetCount() = 1) Then
        m_verts(0) = 0
        m_verts(1) = 0
        RemoveLast = True
        m_bFirstItem = True
    Else
        RemoveLast = False
    End If
End Function

' 根据一个数组来初始化点数组
Public Function SetPoints(ByVal points As Variant) As Boolean
    Debug.Assert (VarType(points) = vbArray + vbDouble)
    Debug.Assert (UBound(points) Mod 2 = 1)
    
    ReDim m_verts(UBound(points))
    Dim i As Integer
    For i = 0 To UBound(points)
        m_verts(i) = points(i)
    Next i
End Function


' 返回第一个点数组
Public Function ToArray() As Variant
    ToArray = m_verts
End Function

' 设置某一个点的坐标
Public Function SetAt(ByVal i As Integer, ByVal point As Variant) As Boolean
    Debug.Assert (VarType(point) = vbArray + vbDouble)
    Debug.Assert (UBound(point) = 1)
    
    If (GetCount() = 0) Then
        SetAt = False
        Exit Function
    Else
        If (i < 0 Or i > GetCount() - 1) Then
            SetAt = False
            Exit Function
        Else
            m_verts(i * 2) = point(0)
            m_verts(i * 2 + 1) = point(1)
        End If
    End If
End Function

' 获得某一个点的坐标
Public Function GetAt(ByVal i As Integer, ByRef point As Variant) As Boolean
    If (i < 0 Or i > GetCount() - 1) Then
        GetAt = False
        Exit Function
    Else
        Dim vert(0 To 1) As Double
        SetPoint2d vert, m_verts(i * 2), m_verts(i * 2 + 1)
        point = vert
        GetAt = True
    End If
End Function

Private Sub Class_Initialize()
    ReDim m_verts(1)
    m_bFirstItem = True
End Sub

Attribute VB_Name = "clsEntityArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_ents() As AcadEntity              ' 实际保存数据的变量
Private m_bFirstItem As Boolean         ' 当前是否添加的是第一个元素

' 获得实体数组中包含的元素个数
Public Function GetCount() As Integer
    If (m_bFirstItem) Then
        GetCount = 0
    Else
        GetCount = UBound(m_ents) + 1
    End If
End Function

' 添加实体
Public Function Append(ByVal ent As AcadEntity)
    ' 第一个实体的空间已经分配，只有后面的实体才增加数组的元素个数
    If (m_bFirstItem) Then
        m_bFirstItem = False
    Else
        ReDim Preserve m_ents(UBound(m_ents) + 1)
    End If
    
    ' 为最后一个实体赋值
    Set m_ents(UBound(m_ents)) = ent
End Function

' 删除实体
Public Function RemoveAt(ByVal i As Integer) As Boolean
    If (i < 0 Or i > GetCount() - 1) Then
        RemoveAt = False
        Exit Function
    Else
        If (i <> GetCount() - 1) Then
            Dim j As Integer
            For j = i To UBound(m_ents) - 1
                Set m_ents(j) = m_ents(j + 1)
            Next j
        End If
        
        If (GetCount() = 1) Then
            Set m_ents(0) = Nothing
            m_bFirstItem = True
        Else
            ReDim Preserve m_ents(UBound(m_ents) - 1)
        End If
    End If
End Function

' 插入实体
Public Function InsertAt(ByVal i As Integer, ByVal ent As AcadEntity) As Boolean
    If (m_bFirstItem) Then
        If (i = 0) Then
            Set m_ents(0) = ent
            m_bFirstItem = False
        Else
            InsertAt = False
            Exit Function
        End If
    Else
        If (i < 0 Or i > GetCount()) Then
            InsertAt = False
            Exit Function
        Else
            ReDim Preserve m_ents(UBound(m_ents) + 1)
            
            If (i <> GetCount()) Then
                Dim j As Integer
                For j = UBound(m_ents) To i + 1 Step -1
                    Set m_ents(j) = m_ents(j - 1)
                Next j
            End If
            
            Set m_ents(1) = ent
            
            InsertAt = True
        End If
    End If
End Function

' 删除最后一个实体
Public Function RemoveLast() As Boolean
    If (GetCount() > 1) Then
        ReDim Preserve m_ents(UBound(m_ents) - 1)
        RemoveLast = True
    ElseIf (GetCount() = 1) Then
        Set m_ents(0) = Nothing
        RemoveLast = True
        m_bFirstItem = True
    Else
        RemoveLast = False
    End If
End Function

' 根据一个数组来初始化实体数组
Public Function SetPoints(ByRef ents() As AcadEntity) As Boolean
    ReDim m_ents(UBound(ents))
    Dim i As Integer
    For i = 0 To UBound(ents)
        Set m_ents(i) = ents(i)
    Next i
End Function

' 返回第一个实体数组
Public Function ToArray() As AcadEntity()
    ToArray = m_ents
End Function

' 修改某一个索引处的实体
Public Function SetAt(ByVal i As Integer, ByVal ent As AcadEntity) As Boolean
    If (GetCount() = 0) Then
        SetAt = False
        Exit Function
    Else
        If (i < 0 Or i > GetCount() - 1) Then
            SetAt = False
            Exit Function
        Else
            Set m_ents(i) = ent
        End If
    End If
End Function

' 获得某一个实体
Public Function GetAt(ByVal i As Integer, ByRef ent As AcadEntity) As Boolean
    If (i < 0 Or i > GetCount() - 1) Then
        GetAt = False
        Exit Function
    Else
        Set ent = m_ents(i)
        GetAt = True
    End If
End Function

Private Sub Class_Initialize()
    ReDim m_ents(0)
    m_bFirstItem = True
End Sub

Attribute VB_Name = "clsMath"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' 2-1
' 角度值转换为弧度值
Public Function DegreeToRadian(ByVal angle As Double) As Double
    DegreeToRadian = angle * PI() / 180
End Function

Public Function PI() As Double
    PI = Atn(1) * 4
End Function

' 2-2
' 计算两个点之间的距离
Public Function GetDistanceBetween2Point(ByVal startPoint As Variant, ByVal endPoint As Variant) As Double
    Dim x As Double, y As Double, z As Double
    x = startPoint(0) - endPoint(0)
    y = startPoint(1) - endPoint(1)
    If (UBound(startPoint) = 2 Or UBound(endPoint) = 2) Then
        z = startPoint(2) - endPoint(2)
    Else
        z = 0
    End If
    
    GetDistanceBetween2Point = Sqr(x ^ 2 + y ^ 2 + z ^ 2)
End Function

' 计算两个点的中点
Public Function GetMiddlePointBetween2Point(ByVal startPoint As Variant, ByVal endPoint As Variant) As Variant
    Dim midPoint(0 To 2) As Double
    midPoint(0) = (startPoint(0) + endPoint(0)) / 2
    midPoint(1) = (startPoint(1) + endPoint(1)) / 2
    midPoint(2) = (startPoint(2) + endPoint(2)) / 2
    
    GetMiddlePointBetween2Point = midPoint
End Function

' 已知三点确定圆心
Public Function GetCenterBy3Point(ByVal startPoint As Variant, ByVal onPoint As Variant, ByVal endPoint As Variant, ByRef centerPoint() As Double) As Boolean
    Dim xysm, xyse, xy As Double
    'Dim center(0 To 2) As Double
    
    xy = startPoint(0) ^ 2 + startPoint(1) ^ 2
    xyse = xy - endPoint(0) ^ 2 - endPoint(1) ^ 2
    xysm = xy - onPoint(0) ^ 2 - onPoint(1) ^ 2
    xy = (startPoint(0) - onPoint(0)) * (startPoint(1) - endPoint(1)) - (startPoint(0) - endPoint(0)) * (startPoint(1) - onPoint(1))

    ' 判断三点是否共线
    If Abs(xy) < 0.000001 Then
        GetCenterBy3Point = False
        Exit Function
    End If
    
    ' 获得圆心
    centerPoint(0) = (xysm * (startPoint(1) - endPoint(1)) - xyse * (startPoint(1) - onPoint(1))) / (2 * xy)
    centerPoint(1) = (xyse * (startPoint(0) - onPoint(0)) - xysm * (startPoint(0) - endPoint(0))) / (2 * xy)
    centerPoint(2) = 0
    'centerPoint = center

    GetCenterBy3Point = True
End Function

' 2-3
' 返回一个数组的最大值和最小值
Public Function MinMaxOfArray(ByRef values() As Double, ByRef min As Double, ByRef max As Double)
    min = values(LBound(values))
    max = min

    Dim i As Integer
    For i = LBound(values) To UBound(values)
        If (values(i) < min) Then
            min = values(i)
        End If
        
        If (values(i) > max) Then
            max = values(i)
        End If
    Next i
End Function










' 判断两个点是否重合
Public Function PointIsEqual(ByVal startPoint As Variant, ByVal endPoint As Variant) As Boolean
    Dim x As Double, y As Double, z As Double
    x = startPoint(0) - endPoint(0)
    y = startPoint(1) - endPoint(1)
    If (UBound(startPoint) = 2 Or UBound(endPoint) = 2) Then
        z = startPoint(2) - endPoint(2)
    Else
        z = 0
    End If
    
    If (x * x + y * y + z * z) > 0.0000001 Then
        PointIsEqual = False
    Else
        PointIsEqual = True
    End If
End Function

' 三维点转换为二维点
Public Function Point3dto2d(ByVal point As Variant) As Variant
    Debug.Assert (VarType(point) = vbArray + vbDouble)
    Debug.Assert (UBound(point) = 2)
    
    Dim point2d(0 To 1) As Double
    SetPoint2d point2d, point(0), point(1)
    
    Point3dto2d = point2d
End Function

Attribute VB_Name = "clsModelSpace"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private math As New clsMath

' 2-1
Public Function AddLine(ByVal startPoint As Variant, ByVal endPoint As Variant) As AcadLine
    ' 参数有效性检查
    Debug.Assert (VarType(startPoint) = vbArray + vbDouble)
    Debug.Assert (VarType(endPoint) = vbArray + vbDouble)

    ' 创建直线对象
    Set AddLine = ThisDrawing.ModelSpace.AddLine(startPoint, endPoint)
End Function

Public Function AddLineByAngleAndLength(ByVal startPoint As Variant, ByVal angle As Double, ByVal length As Double) As AcadLine
    ' 将角度转换成弧度
    Dim util As New clsUtiltiy
    angle = util.DegreeToRadian(angle)

    ' 计算直线的终点
    Dim endPoint(0 To 2) As Double
    SetPoint3d endPoint, startPoint(0) + length * Cos(angle), startPoint(1) + length * Sin(angle), startPoint(2)
    
    ' 创建直线对象
    Set AddLineByAngleAndLength = AddLine(startPoint, endPoint)
End Function

' 2-2
Public Function AddCircle(ByVal centerPoint As Variant, ByVal radius As Double) As AcadCircle
    Debug.Assert (radius > 0.0000001)
    Debug.Assert (VarType(centerPoint) = vbArray + vbDouble)
    
    Set AddCircle = ThisDrawing.ModelSpace.AddCircle(centerPoint, radius)
End Function

' 两点法画圆
Public Function AddCircleBy2Point(ByVal startPoint As Variant, ByVal endPoint As Variant) As AcadCircle
    Debug.Assert (VarType(startPoint) = vbArray + vbDouble)
    Debug.Assert (VarType(endPoint) = vbArray + vbDouble)
    
    ' 计算圆心和半径
    Dim centerPoint As Variant, radius As Double
    centerPoint = math.GetMiddlePointBetween2Point(startPoint, endPoint)
    radius = math.GetDistanceBetween2Point(startPoint, endPoint) / 2
    
    Set AddCircleBy2Point = AddCircle(centerPoint, radius)
End Function

' 三点画圆
Public Function AddCircleBy3Point(ByVal startPoint As Variant, ByVal onPoint As Variant, ByVal endPoint As Variant) As AcadCircle
    Debug.Assert (VarType(startPoint) = vbArray + vbDouble)
    Debug.Assert (VarType(onPoint) = vbArray + vbDouble)
    Debug.Assert (VarType(endPoint) = vbArray + vbDouble)
    
    ' 计算圆心
    Dim centerPoint(0 To 2) As Double
    If (Not math.GetCenterBy3Point(startPoint, onPoint, endPoint, centerPoint)) Then
        MsgBox "在AddCircleBy3Point函数中，由于指定的三点共线，创建圆失败！"
        Exit Function
    End If
    
    ' 计算半径
    Dim radius As Double
    radius = math.GetDistanceBetween2Point(centerPoint, startPoint)
    
    Set AddCircleBy3Point = AddCircle(centerPoint, radius)
End Function

' 绘制圆弧
' startAngle: endAngle: 均为弧度值
Public Function AddArc(ByVal centerPoint As Variant, ByVal radius As Double, ByVal startAngle As Double, ByVal endAngle As Double) As AcadArc
    Debug.Assert (VarType(centerPoint) = vbArray + vbDouble)
    Debug.Assert (radius > 0)
    
    Set AddArc = ThisDrawing.ModelSpace.AddArc(centerPoint, radius, startAngle, endAngle)
End Function

Public Function AddArcByCenterStartEndPoint(ByVal centerPoint As Variant, ByVal startPoint As Variant, ByVal endPoint As Variant) As AcadArc
    Debug.Assert (VarType(centerPoint) = vbArray + vbDouble)
    Debug.Assert (VarType(startPoint) = vbArray + vbDouble)
    Debug.Assert (VarType(endPoint) = vbArray + vbDouble)
    
    Dim radius1 As Double, radius2 As Double
    radius1 = math.GetDistanceBetween2Point(centerPoint, startPoint)
    radius2 = math.GetDistanceBetween2Point(centerPoint, endPoint)
    Debug.Assert (Abs(radius1 - radius2) < 0.0000001)
    
    ' 计算起始和终止角度
    Dim startAngle As Double, endAngle As Double
    startAngle = ThisDrawing.Utility.AngleFromXAxis(centerPoint, startPoint)
    endAngle = ThisDrawing.Utility.AngleFromXAxis(centerPoint, endPoint)
    
    Set AddArcByCenterStartEndPoint = AddArc(centerPoint, radius1, startAngle, endAngle)
End Function

Public Function AddArcByCenterStartPointAndArcLength(ByVal centerPoint As Variant, ByVal startPoint As Variant, ByVal arcLength As Double) As AcadArc
    Debug.Assert (VarType(centerPoint) = vbArray + vbDouble)
    Debug.Assert (VarType(startPoint) = vbArray + vbDouble)
    Debug.Assert (arcLength > 0)
    
    Dim radius As Double
    radius = math.GetDistanceBetween2Point(centerPoint, startPoint)
    
    Dim startAngle As Double, endAngle As Double
    startAngle = ThisDrawing.Utility.AngleFromXAxis(centerPoint, startPoint)
    endAngle = arcLength / radius + startAngle
    
    Set AddArcByCenterStartPointAndArcLength = AddArc(centerPoint, radius, startAngle, endAngle)
End Function

' 三点法绘制圆弧
Public Function AddArcBy3Point(ByVal startPoint As Variant, ByVal onPoint As Variant, ByVal endPoint As Variant) As AcadArc
    Debug.Assert (VarType(startPoint) = vbArray + vbDouble)
    Debug.Assert (VarType(onPoint) = vbArray + vbDouble)
    Debug.Assert (VarType(endPoint) = vbArray + vbDouble)
    
    ' 计算圆心
    Dim centerPoint(0 To 2) As Double
    If (Not math.GetCenterBy3Point(startPoint, onPoint, endPoint, centerPoint)) Then
        MsgBox "在AddCircleBy3Point函数中，由于指定的三点共线，创建圆失败！"
        Exit Function
    End If
    
    ' 计算半径
    Dim radius As Double
    radius = math.GetDistanceBetween2Point(centerPoint, startPoint)
    
    ' 计算起始和终止角度
    Dim startAngle As Double, endAngle As Double
    startAngle = ThisDrawing.Utility.AngleFromXAxis(centerPoint, startPoint)
    endAngle = ThisDrawing.Utility.AngleFromXAxis(centerPoint, endPoint)
    
    Set AddArcBy3Point = AddArc(centerPoint, radius, startAngle, endAngle)
End Function

' 2-3
' 多段线基准函数
Public Function AddLWPolyline(ByVal verts As Variant, Optional closed As Boolean = False, Optional width As Double = 0) As AcadLWPolyline
    Debug.Assert (VarType(verts) = vbArray + vbDouble)
    Debug.Assert (UBound(verts) > 2 And UBound(verts) Mod 2 = 1)
    
    Set AddLWPolyline = ThisDrawing.ModelSpace.AddLightWeightPolyline(verts)
    If (closed) Then
        AddLWPolyline.closed = True
    End If
    AddLWPolyline.ConstantWidth = width
End Function

' 创建矩形
Public Function AddRectangle(ByVal point1 As Variant, ByVal point2 As Variant) As AcadLWPolyline
    Dim x(0 To 1) As Double, y(0 To 1) As Double
    SetPoint2d x, point1(0), point2(0)
    SetPoint2d y, point1(1), point2(1)
    
    Dim xMin As Double, xMax As Double, yMin As Double, yMax As Double
    math.MinMaxOfArray x, xMin, xMax
    math.MinMaxOfArray y, yMin, yMax
    
    Dim point(0 To 1) As Double
    SetPoint2d point, xMin, yMin
    Dim pointList As New cls2dPointArray
    pointList.Append point
    SetPoint2d point, xMax, yMin
    pointList.Append point
    SetPoint2d point, xMax, yMax
    pointList.Append point
    SetPoint2d point, xMin, yMax
    pointList.Append point
    
    AddLWPolyline pointList.ToArray(), True
End Function

Public Function AddRectangle1(ByVal point1 As Variant, ByVal point2 As Variant) As AcadLWPolyline
    Dim x(0 To 1) As Double, y(0 To 1) As Double
    SetPoint2d x, point1(0), point2(0)
    SetPoint2d y, point1(1), point2(1)
    
    Dim xMin As Double, xMax As Double, yMin As Double, yMax As Double
    math.MinMaxOfArray x, xMin, xMax
    math.MinMaxOfArray y, yMin, yMax
    
    Dim points(0 To 7) As Double
    points(0) = xMin
    points(1) = yMin
    points(2) = xMax
    points(3) = yMin
    points(4) = xMax
    points(5) = yMax
    points(6) = xMin
    points(7) = yMax
    
    AddLWPolyline points, True
End Function

' 创建多边形
Public Function AddPolygon(ByVal centerPoint As Variant, ByVal sideCount As Integer, ByVal radius As Double, _
    Optional width As Double = 0, Optional angle As Double = 0) As AcadLWPolyline
    ' 计算每条边对应的角度
    Dim sideAngle As Double
    sideAngle = 2 * math.PI() / sideCount
    
    ' 构建顶点数组
    Dim verts As New cls2dPointArray
    Dim i As Integer
    Dim point(0 To 1) As Double
    For i = 0 To 2 * sideCount - 1
        If i Mod 2 = 0 Then
            point(0) = centerPoint(0) + radius * Cos((i \ 2) * sideAngle)
        Else
            point(1) = centerPoint(1) + radius * Sin((i \ 2) * sideAngle)
            verts.Append point
        End If
    Next i
    
    Set AddPolygon = AddLWPolyline(verts.ToArray(), True, width)
    AddPolygon.Rotate centerPoint, angle
    AddPolygon.Update
End Function

' 创建箭头
Public Function AddLeaderByPolyline(ByVal startPoint As Variant, ByVal endPoint As Variant, _
    Optional widthScale As Double = 0.3) As AcadLWPolyline
    Debug.Assert (VarType(startPoint) = vbArray + vbDouble)
    Debug.Assert (VarType(endPoint) = vbArray + vbDouble)
    Debug.Assert (UBound(startPoint) = 1)
    Debug.Assert (UBound(endPoint) = 1)
    
    Dim verts As New cls2dPointArray
    verts.Append startPoint
    verts.Append endPoint
    
    Set AddLeaderByPolyline = AddLWPolyline(verts.ToArray())
    
    Dim length As Double
    length = math.GetDistanceBetween2Point(startPoint, endPoint)
    AddLeaderByPolyline.SetWidth 0, length * widthScale, 0
End Function

' 2-4
' 创建面域
Public Function AddRegion(ByRef ents() As AcadEntity, ByRef regions As Variant, ByRef count As Integer) As Boolean
    On Error GoTo ErrHandle
    
    regions = ThisDrawing.ModelSpace.AddRegion(ents)
    count = UBound(regions) + 1
    AddRegion = True
    
    Exit Function
    
ErrHandle:
    If Err.Number = -2145386493 Then
        Debug.Print "AddRegion函数：面域定义边界未闭合！"
        count = -1
        AddRegion = False
    End If
    Err.Clear
End Function

'
'
'
'
'

'
' 获得一条直线或圆的起终点和凸度
Private Function GetStartEndPointAndBulge(ByVal ent As AcadEntity, ByVal bReverseBulge As Boolean, _
    ByRef startPoint As Variant, ByRef endPoint As Variant, ByRef bulge As Double) As Boolean
    If TypeOf ent Is AcadLine Then
        Dim line As AcadLine
        Set line = ent
        startPoint = line.startPoint
        endPoint = line.endPoint
        bulge = 0
        
        GetStartEndPointAndBulge = True
    ElseIf TypeOf ent Is AcadArc Then
        Dim arc As AcadArc
        Set arc = ent
        startPoint = arc.startPoint
        endPoint = arc.endPoint
        If (bReverseBulge) Then
            bulge = Tan(-arc.TotalAngle / 4)
        Else
            bulge = Tan(arc.TotalAngle / 4)
        End If
        
        GetStartEndPointAndBulge = True
    Else
        GetStartEndPointAndBulge = False
    End If
End Function

' 根据多条首尾相连的线创建闭合多段线
Public Function AddLWPolylineByEnts(ByRef ents() As AcadEntity, ByRef poly As AcadLWPolyline) As Boolean
    ' 用一个动态数组来保存边界对象
    Dim entArray As New clsEntityArray
    Dim i As Integer
    For i = 0 To UBound(ents)
        entArray.Append ents(i)
    Next i
    
    ' 根据第一个实体创建多段线
    Dim verts As New cls2dPointArray
    Dim startPoint As Variant, endPoint As Variant, bulge As Double
    Dim mSpace As New clsModelSpace
    If (GetStartEndPointAndBulge(ents(0), False, startPoint, endPoint, bulge)) Then
        verts.Append startPoint
        verts.Append endPoint
        Set poly = mSpace.AddLWPolyline(verts.ToArray())
        
        poly.SetBulge 0, bulge
    Else
        AddLWPolylineByEnts = False
        Exit Function
    End If
    
    entArray.RemoveAt 0
    
    ' 从一个实体开始，不断添加多段线的顶点
    Dim vertCount As Integer        ' 多段线顶点的个数
    vertCount = 2
    Dim previousPoint As Variant
    previousPoint = endPoint
    Dim math As New clsMath
    
ARRAYLOOP:
    For i = 0 To entArray.GetCount - 1
        Dim ent As AcadEntity
        entArray.GetAt i, ent
        
        ' 判断当前实体的起点或终点是否和上一个顶点重合
        If (GetStartEndPointAndBulge(ent, False, startPoint, endPoint, bulge)) Then
            If (math.PointIsEqual(previousPoint, startPoint)) Then
                poly.AddVertex vertCount, math.Point3dto2d(endPoint)
                poly.SetBulge vertCount - 1, bulge
                previousPoint = endPoint
                
                vertCount = vertCount + 1
                entArray.RemoveAt i
                GoTo ARRAYLOOP
            ElseIf (math.PointIsEqual(previousPoint, endPoint)) Then
                GetStartEndPointAndBulge ent, True, startPoint, endPoint, bulge
                poly.AddVertex vertCount, math.Point3dto2d(startPoint)
                poly.SetBulge vertCount - 1, bulge
                previousPoint = startPoint
                
                vertCount = vertCount + 1
                entArray.RemoveAt i
                GoTo ARRAYLOOP
            End If
            
        End If
    Next i
    
    If i = 0 Then
        AddLWPolylineByEnts = True
    Else
        AddLWPolylineByEnts = False
    End If
End Function

'
'
'
'

'
'

'
''

'
'
'
'


'
'
'

'
'
'
'

'

Attribute VB_Name = "mdlUtility"
Option Explicit

' 2-1
' 设置三维点的坐标值
Public Function SetPoint3d(ByRef point As Variant, ByVal x As Double, ByVal y As Double, ByVal z As Double)
    Debug.Assert (VarType(point) = vbArray + vbDouble)
    Debug.Assert (LBound(point) = 0 And UBound(point) = 2)

    point(0) = x
    point(1) = y
    point(2) = z
End Function

' 2-3
' 设置二维点坐标值（为包括两个元素的一维数组赋值）
Public Function SetPoint2d(ByRef point As Variant, ByVal x As Double, ByVal y As Double)
    Debug.Assert (VarType(point) = vbArray + vbDouble)
    Debug.Assert (LBound(point) = 0 And UBound(point) = 1)
    
    point(0) = x
    point(1) = y
End Function
