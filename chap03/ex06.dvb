Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit

Public Sub ComDialog()
    frmMain.Show
End Sub

Public Sub TestAPICommonDialog()
    Dim commonDlg As New clsCommonDialog
    
    Dim fileName As String
    commonDlg.OpenFile fileName
    MsgBox fileName
    
    commonDlg.SaveFile fileName
    MsgBox fileName
End Sub

Attribute VB_Name = "cls2dPointArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_verts() As Double             ' 实际保存数据的变量
Private m_bFirstItem As Boolean         ' 当前是否添加的是第一个元素

' 获得点数组中包含的点数
Public Function GetCount() As Integer
    If (m_bFirstItem) Then
        GetCount = 0
    Else
        GetCount = (UBound(m_verts) + 1) / 2
    End If
End Function

' 添加点
Public Function Append(ByVal point As Variant)
    Debug.Assert (VarType(point) = vbArray + vbDouble)
    Debug.Assert (UBound(point) >= 1)
   
    ' 第一个点的空间已经分配，只有后面的点才增加数组的元素个数
    If (m_bFirstItem) Then
        m_bFirstItem = False
    Else
        ReDim Preserve m_verts(UBound(m_verts) + 2)
    End If
    
    ' 为最后一个点赋值
    m_verts(UBound(m_verts) - 1) = point(0)
    m_verts(UBound(m_verts)) = point(1)
End Function

' 删除点
Public Function RemoveAt(ByVal i As Integer) As Boolean
    If (i < 0 Or i > GetCount() - 1) Then
        RemoveAt = False
        Exit Function
    Else
        If (i <> GetCount() - 1) Then
            Dim j As Integer
            For j = i * 2 To UBound(m_verts) - 2
                m_verts(j) = m_verts(j + 2)
            Next j
        End If
        
        If (GetCount() = 1) Then
            m_verts(0) = 0
            m_verts(1) = 0
            m_bFirstItem = True
        Else
            ReDim Preserve m_verts(UBound(m_verts) - 2)
        End If
    End If
End Function

' 插入点
Public Function InsertAt(ByVal i As Integer, ByVal point As Variant) As Boolean
    Debug.Assert (VarType(point) = vbArray + vbDouble)
    Debug.Assert (UBound(point) >= 1)
    
    If (m_bFirstItem) Then
        If (i = 0) Then
            m_verts(0) = point(0)
            m_verts(1) = point(1)
            m_bFirstItem = False
        Else
            InsertAt = False
            Exit Function
        End If
    Else
        If (i < 0 Or i > GetCount()) Then
            InsertAt = False
            Exit Function
        Else
            ReDim Preserve m_verts(UBound(m_verts) + 2)
            
            If (i <> GetCount()) Then
                Dim j As Integer
                For j = UBound(m_verts) To (i + 1) * 2 Step -1
                    m_verts(j) = m_verts(j - 2)
                Next j
            End If
            
            m_verts(i * 2) = point(0)
            m_verts(i * 2 + 1) = point(1)
            
            InsertAt = True
        End If
    End If
End Function

' 删除最后一个点
Public Function RemoveLast() As Boolean
    If (GetCount() > 1) Then
        ReDim Preserve m_verts(UBound(m_verts) - 2)
        RemoveLast = True
    ElseIf (GetCount() = 1) Then
        m_verts(0) = 0
        m_verts(1) = 0
        RemoveLast = True
        m_bFirstItem = True
    Else
        RemoveLast = False
    End If
End Function

' 根据一个数组来初始化点数组
Public Function SetPoints(ByVal points As Variant) As Boolean
    Debug.Assert (VarType(points) = vbArray + vbDouble)
    Debug.Assert (UBound(points) Mod 2 = 1)
    
    ReDim m_verts(UBound(points))
    Dim i As Integer
    For i = 0 To UBound(points)
        m_verts(i) = points(i)
    Next i
End Function


' 返回第一个点数组
Public Function ToArray() As Variant
    ToArray = m_verts
End Function

' 设置某一个点的坐标
Public Function SetAt(ByVal i As Integer, ByVal point As Variant) As Boolean
    Debug.Assert (VarType(point) = vbArray + vbDouble)
    Debug.Assert (UBound(point) = 1)
    
    If (GetCount() = 0) Then
        SetAt = False
        Exit Function
    Else
        If (i < 0 Or i > GetCount() - 1) Then
            SetAt = False
            Exit Function
        Else
            m_verts(i * 2) = point(0)
            m_verts(i * 2 + 1) = point(1)
        End If
    End If
End Function

' 获得某一个点的坐标
Public Function GetAt(ByVal i As Integer, ByRef point As Variant) As Boolean
    If (i < 0 Or i > GetCount() - 1) Then
        GetAt = False
        Exit Function
    Else
        Dim vert(0 To 1) As Double
        SetPoint2d vert, m_verts(i * 2), m_verts(i * 2 + 1)
        point = vert
        GetAt = True
    End If
End Function

Private Sub Class_Initialize()
    ReDim m_verts(1)
    m_bFirstItem = True
End Sub

Attribute VB_Name = "cls3dPointArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' 2-8
Private m_verts() As Double             ' 实际保存数据的变量
Private m_bFirstItem As Boolean         ' 当前是否添加的是第一个元素

' 获得点数组中包含的点数
Public Function GetCount() As Integer
    If (m_bFirstItem) Then
        GetCount = 0
    Else
        GetCount = (UBound(m_verts) + 1) / 3
    End If
End Function

' 添加点
Public Function Append(ByVal point As Variant)
    Debug.Assert (VarType(point) = vbArray + vbDouble)
    Debug.Assert (UBound(point) >= 2)
   
    ' 第一个点的空间已经分配，只有后面的点才增加数组的元素个数
    If (m_bFirstItem) Then
        m_bFirstItem = False
    Else
        ReDim Preserve m_verts(UBound(m_verts) + 3)
    End If
    
    ' 为最后一个点赋值
    m_verts(UBound(m_verts) - 2) = point(0)
    m_verts(UBound(m_verts) - 1) = point(1)
    m_verts(UBound(m_verts)) = point(2)
End Function

' 删除点
Public Function RemoveAt(ByVal i As Integer) As Boolean
    If (i < 0 Or i > GetCount() - 1) Then
        RemoveAt = False
        Exit Function
    Else
        If (i <> GetCount() - 1) Then
            Dim j As Integer
            For j = i * 3 To UBound(m_verts) - 3
                m_verts(j) = m_verts(j + 3)
            Next j
        End If
        
        If (GetCount() = 1) Then
            m_verts(0) = 0
            m_verts(1) = 0
            m_verts(2) = 0
            m_bFirstItem = True
        Else
            ReDim Preserve m_verts(UBound(m_verts) - 3)
        End If
    End If
End Function

' 插入点
Public Function InsertAt(ByVal i As Integer, ByVal point As Variant) As Boolean
    Debug.Assert (VarType(point) = vbArray + vbDouble)
    Debug.Assert (UBound(point) >= 2)
    
    If (m_bFirstItem) Then
        If (i = 0) Then
            m_verts(0) = point(0)
            m_verts(1) = point(1)
            m_verts(2) = point(2)
            m_bFirstItem = False
        Else
            InsertAt = False
            Exit Function
        End If
    Else
        If (i < 0 Or i > GetCount()) Then
            InsertAt = False
            Exit Function
        Else
            ReDim Preserve m_verts(UBound(m_verts) + 3)
            
            If (i <> GetCount()) Then
                Dim j As Integer
                For j = UBound(m_verts) To (i + 1) * 3 Step -1
                    m_verts(j) = m_verts(j - 3)
                Next j
            End If
            
            m_verts(i * 3) = point(0)
            m_verts(i * 3 + 1) = point(1)
            m_verts(i * 3 + 2) = point(2)
            
            InsertAt = True
        End If
    End If
End Function

' 删除最后一个点
Public Function RemoveLast() As Boolean
    If (GetCount() > 1) Then
        ReDim Preserve m_verts(UBound(m_verts) - 3)
        RemoveLast = True
    ElseIf (GetCount() = 1) Then
        m_verts(0) = 0
        m_verts(1) = 0
        m_verts(2) = 0
        RemoveLast = True
        m_bFirstItem = True
    Else
        RemoveLast = False
    End If
End Function

' 根据一个数组来初始化点数组
Public Function SetPoints(ByVal points As Variant) As Boolean
    Debug.Assert (VarType(points) = vbArray + vbDouble)
    Debug.Assert (UBound(points) Mod 3 = 2)
    
    ReDim m_verts(UBound(points))
    Dim i As Integer
    For i = 0 To UBound(points)
        m_verts(i) = points(i)
    Next i
End Function


' 返回第一个点数组
Public Function ToArray() As Variant
    ToArray = m_verts
End Function

' 设置某一个点的坐标
Public Function SetAt(ByVal i As Integer, ByVal point As Variant) As Boolean
    Debug.Assert (VarType(point) = vbArray + vbDouble)
    Debug.Assert (UBound(point) = 2)
    
    If (GetCount() = 0) Then
        SetAt = False
        Exit Function
    Else
        If (i < 0 Or i > GetCount() - 1) Then
            SetAt = False
            Exit Function
        Else
            m_verts(i * 3) = point(0)
            m_verts(i * 3 + 1) = point(1)
            m_verts(i * 3 + 2) = point(2)
        End If
    End If
End Function

' 获得某一个点的坐标
Public Function GetAt(ByVal i As Integer, ByRef point As Variant) As Boolean
    If (i < 0 Or i > GetCount() - 1) Then
        GetAt = False
        Exit Function
    Else
        Dim vert(0 To 2) As Double
        SetPoint3d vert, m_verts(i * 3), m_verts(i * 3 + 1), m_verts(i * 3 + 2)
        point = vert
        GetAt = True
    End If
End Function

Private Sub Class_Initialize()
    ReDim m_verts(2)
    m_bFirstItem = True
End Sub

Attribute VB_Name = "clsCommonDialog"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private Declare Function GetOpenFileName Lib "comdlg32.dll" Alias "GetOpenFileNameA" (pOpenfilename As OPENFILENAME) As Long
Private Declare Function GetSaveFileName Lib "comdlg32.dll" Alias "GetSaveFileNameA" (pOpenfilename As OPENFILENAME) As Long
 
Private Type OPENFILENAME
     lStructSize As Long
     hwndOwner As Long
     hInstance As Long
     lpstrFilter As String
     lpstrCustomFilter As String
     nMaxCustFilter As Long
     nFilterIndex As Long
     lpstrFile As String
     nMaxFile As Long
     lpstrFileTitle As String
     nMaxFileTitle As Long
     lpstrInitialDir As String
     lpstrTitle As String
     flags As Long
     nFileOffset As Integer
     nFileExtension As Integer
     lpstrDefExt As String
     lCustData As Long
     lpfnHook As Long
     lpTemplateName As String
End Type

' 打开文件对话框
Public Function OpenFile(ByRef strFileName As String) As Boolean
    Dim ofn As OPENFILENAME

    ofn.lStructSize = Len(ofn)
    ofn.lpstrFilter = "数据库文件(*.mdb)" & Chr(0) & "*.mdb" & Chr(0)   ' 扩展名
    ofn.lpstrFile = Space(254)
    ofn.nMaxFile = 255
    ofn.lpstrFileTitle = Space(254)
    ofn.nMaxFileTitle = 255
    ofn.lpstrInitialDir = "C:\"
    ofn.lpstrTitle = "打开文件"
    ofn.flags = 6148

    Dim rt As Long
    rt = GetOpenFileName(ofn)
    
    If rt >= 1 Then
        strFileName = ofn.lpstrFile
        strFileName = Left(strFileName, InStr(strFileName, Chr(0)) - 1)
        
        OpenFile = True
    Else
        strFileName = ""
        OpenFile = False
    End If
End Function

' 保存文件对话框
Public Function SaveFile(ByRef strFileName As String) As Boolean
    Dim ofn As OPENFILENAME

    ofn.lStructSize = Len(ofn)
    ofn.lpstrFilter = "表格文件(*.xls)" & Chr(0) & "*.xls" & Chr(0) ' 扩展名
    ofn.lpstrFile = Space(254)
    ofn.nMaxFile = 255
    ofn.lpstrFileTitle = Space(254)
    ofn.nMaxFileTitle = 255
    ofn.lpstrInitialDir = "C:\"
    ofn.lpstrTitle = "保存文件"
    ofn.flags = 6148

    Dim rt As Long
    rt = GetSaveFileName(ofn)
    
    If rt >= 1 Then
        strFileName = ofn.lpstrFile
        strFileName = Left(strFileName, InStr(strFileName, Chr(0)) - 1)
        If StrComp(Right(strFileName, 3), "xls", vbTextCompare) <> 0 Then
            strFileName = strFileName & ".xls"
        End If
        
        SaveFile = True
    Else
        strFileName = ""
        SaveFile = False
    End If
End Function

Attribute VB_Name = "clsEntityArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_ents() As AcadEntity              ' 实际保存数据的变量
Private m_bFirstItem As Boolean         ' 当前是否添加的是第一个元素

' 获得实体数组中包含的元素个数
Public Function GetCount() As Integer
    If (m_bFirstItem) Then
        GetCount = 0
    Else
        GetCount = UBound(m_ents) + 1
    End If
End Function

' 添加实体
Public Function Append(ByVal ent As AcadEntity)
    ' 第一个实体的空间已经分配，只有后面的实体才增加数组的元素个数
    If (m_bFirstItem) Then
        m_bFirstItem = False
    Else
        ReDim Preserve m_ents(UBound(m_ents) + 1)
    End If
    
    ' 为最后一个实体赋值
    Set m_ents(UBound(m_ents)) = ent
End Function

' 删除实体
Public Function RemoveAt(ByVal i As Integer) As Boolean
    If (i < 0 Or i > GetCount() - 1) Then
        RemoveAt = False
        Exit Function
    Else
        If (i <> GetCount() - 1) Then
            Dim j As Integer
            For j = i To UBound(m_ents) - 1
                Set m_ents(j) = m_ents(j + 1)
            Next j
        End If
        
        If (GetCount() = 1) Then
            Set m_ents(0) = Nothing
            m_bFirstItem = True
        Else
            ReDim Preserve m_ents(UBound(m_ents) - 1)
        End If
    End If
End Function

' 插入实体
Public Function InsertAt(ByVal i As Integer, ByVal ent As AcadEntity) As Boolean
    If (m_bFirstItem) Then
        If (i = 0) Then
            Set m_ents(0) = ent
            m_bFirstItem = False
        Else
            InsertAt = False
            Exit Function
        End If
    Else
        If (i < 0 Or i > GetCount()) Then
            InsertAt = False
            Exit Function
        Else
            ReDim Preserve m_ents(UBound(m_ents) + 1)
            
            If (i <> GetCount()) Then
                Dim j As Integer
                For j = UBound(m_ents) To i + 1 Step -1
                    Set m_ents(j) = m_ents(j - 1)
                Next j
            End If
            
            Set m_ents(1) = ent
            
            InsertAt = True
        End If
    End If
End Function

' 删除最后一个实体
Public Function RemoveLast() As Boolean
    If (GetCount() > 1) Then
        ReDim Preserve m_ents(UBound(m_ents) - 1)
        RemoveLast = True
    ElseIf (GetCount() = 1) Then
        Set m_ents(0) = Nothing
        RemoveLast = True
        m_bFirstItem = True
    Else
        RemoveLast = False
    End If
End Function

' 根据一个数组来初始化实体数组
Public Function SetPoints(ByRef ents() As AcadEntity) As Boolean
    ReDim m_ents(UBound(ents))
    Dim i As Integer
    For i = 0 To UBound(ents)
        Set m_ents(i) = ents(i)
    Next i
End Function

' 返回第一个实体数组
Public Function ToArray() As AcadEntity()
    ToArray = m_ents
End Function

' 修改某一个索引处的实体
Public Function SetAt(ByVal i As Integer, ByVal ent As AcadEntity) As Boolean
    If (GetCount() = 0) Then
        SetAt = False
        Exit Function
    Else
        If (i < 0 Or i > GetCount() - 1) Then
            SetAt = False
            Exit Function
        Else
            Set m_ents(i) = ent
        End If
    End If
End Function

' 获得某一个实体
Public Function GetAt(ByVal i As Integer, ByRef ent As AcadEntity) As Boolean
    If (i < 0 Or i > GetCount() - 1) Then
        GetAt = False
        Exit Function
    Else
        Set ent = m_ents(i)
        GetAt = True
    End If
End Function

Private Sub Class_Initialize()
    ReDim m_ents(0)
    m_bFirstItem = True
End Sub

Attribute VB_Name = "clsMath"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' 2-1
' 角度值转换为弧度值
'Public Function DegreeToRadian(ByVal angle As Double) As Double
'    DegreeToRadian = angle * PI() / 180
'End Function

Public Function PI() As Double
    PI = Atn(1) * 4
End Function

' 2-2
' 计算两个点之间的距离
Public Function GetDistanceBetween2Point(ByVal startPoint As Variant, ByVal endPoint As Variant) As Double
    Dim x As Double, y As Double, z As Double
    x = startPoint(0) - endPoint(0)
    y = startPoint(1) - endPoint(1)
    If (UBound(startPoint) = 2 Or UBound(endPoint) = 2) Then
        z = startPoint(2) - endPoint(2)
    Else
        z = 0
    End If
    
    GetDistanceBetween2Point = Sqr(x ^ 2 + y ^ 2 + z ^ 2)
End Function

' 计算两个点的中点
Public Function GetMiddlePointBetween2Point(ByVal startPoint As Variant, ByVal endPoint As Variant) As Variant
    Dim midPoint(0 To 2) As Double
    midPoint(0) = (startPoint(0) + endPoint(0)) / 2
    midPoint(1) = (startPoint(1) + endPoint(1)) / 2
    midPoint(2) = (startPoint(2) + endPoint(2)) / 2
    
    GetMiddlePointBetween2Point = midPoint
End Function

' 已知三点确定圆心
Public Function GetCenterBy3Point(ByVal startPoint As Variant, ByVal onPoint As Variant, ByVal endPoint As Variant, ByRef centerPoint() As Double) As Boolean
    Dim xysm, xyse, xy As Double
    'Dim center(0 To 2) As Double
    
    xy = startPoint(0) ^ 2 + startPoint(1) ^ 2
    xyse = xy - endPoint(0) ^ 2 - endPoint(1) ^ 2
    xysm = xy - onPoint(0) ^ 2 - onPoint(1) ^ 2
    xy = (startPoint(0) - onPoint(0)) * (startPoint(1) - endPoint(1)) - (startPoint(0) - endPoint(0)) * (startPoint(1) - onPoint(1))

    ' 判断三点是否共线
    If Abs(xy) < 0.000001 Then
        GetCenterBy3Point = False
        Exit Function
    End If
    
    ' 获得圆心
    centerPoint(0) = (xysm * (startPoint(1) - endPoint(1)) - xyse * (startPoint(1) - onPoint(1))) / (2 * xy)
    centerPoint(1) = (xyse * (startPoint(0) - onPoint(0)) - xysm * (startPoint(0) - endPoint(0))) / (2 * xy)
    centerPoint(2) = 0
    'centerPoint = center

    GetCenterBy3Point = True
End Function

' 2-3
' 返回一个数组的最大值和最小值
Public Function MinMaxOfArray(ByRef values() As Double, ByRef min As Double, ByRef max As Double)
    min = values(LBound(values))
    max = min

    Dim i As Integer
    For i = LBound(values) To UBound(values)
        If (values(i) < min) Then
            min = values(i)
        End If
        
        If (values(i) > max) Then
            max = values(i)
        End If
    Next i
End Function

' 2-10
' 交换两个实数的值
Public Function SwapDouble(ByRef a As Double, ByRef b As Double)
    Dim c As Double
    c = a
    a = b
    b = c
End Function

' 判断两个点是否重合
Public Function PointIsEqual(ByVal startPoint As Variant, ByVal endPoint As Variant) As Boolean
    Dim x As Double, y As Double, z As Double
    x = startPoint(0) - endPoint(0)
    y = startPoint(1) - endPoint(1)
    If (UBound(startPoint) = 2 Or UBound(endPoint) = 2) Then
        z = startPoint(2) - endPoint(2)
    Else
        z = 0
    End If
    
    If (x * x + y * y + z * z) > 0.0000001 Then
        PointIsEqual = False
    Else
        PointIsEqual = True
    End If
End Function

' 三维点转换为二维点
Public Function Point3dto2d(ByVal point As Variant) As Variant
    Debug.Assert (VarType(point) = vbArray + vbDouble)
    Debug.Assert (UBound(point) = 2)
    
    Dim point2d(0 To 1) As Double
    SetPoint2d point2d, point(0), point(1)
    
    Point3dto2d = point2d
End Function

' 3-1
' 角度转弧度
Public Function DegreeToRadian(ByVal angle As Double) As Double
    DegreeToRadian = ThisDrawing.Utility.AngleToReal(CStr(angle), acDegrees)
End Function

' 弧度转角度
Public Function RadianToDegree(ByVal angle As Double, Optional precision As Integer = 2) As Double
    RadianToDegree = CDbl(Val(ThisDrawing.Utility.AngleToString(angle, acDegrees, precision)))
End Function

Attribute VB_Name = "clsModelSpace"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private math As New clsMath

Public Enum TextLocation
    TextTop = 0
    TextBottom = 1
    TextLeft = 2
    TextRight = 3
End Enum

' 2-1
Public Function AddLine(ByVal startPoint As Variant, ByVal endPoint As Variant) As AcadLine
    ' 参数有效性检查
    Debug.Assert (VarType(startPoint) = vbArray + vbDouble)
    Debug.Assert (VarType(endPoint) = vbArray + vbDouble)

    ' 创建直线对象
    Set AddLine = ThisDrawing.ModelSpace.AddLine(startPoint, endPoint)
End Function

Public Function AddLineByAngleAndLength(ByVal startPoint As Variant, ByVal angle As Double, ByVal length As Double) As AcadLine
    ' 将角度转换成弧度
    Dim util As New clsUtiltiy
    angle = util.DegreeToRadian(angle)

    ' 计算直线的终点
    Dim endPoint(0 To 2) As Double
    SetPoint3d endPoint, startPoint(0) + length * Cos(angle), startPoint(1) + length * Sin(angle), startPoint(2)
    
    ' 创建直线对象
    Set AddLineByAngleAndLength = AddLine(startPoint, endPoint)
End Function

' 2-2
Public Function AddCircle(ByVal centerPoint As Variant, ByVal radius As Double) As AcadCircle
    Debug.Assert (radius > 0.0000001)
    Debug.Assert (VarType(centerPoint) = vbArray + vbDouble)
    
    Set AddCircle = ThisDrawing.ModelSpace.AddCircle(centerPoint, radius)
End Function

' 两点法画圆
Public Function AddCircleBy2Point(ByVal startPoint As Variant, ByVal endPoint As Variant) As AcadCircle
    Debug.Assert (VarType(startPoint) = vbArray + vbDouble)
    Debug.Assert (VarType(endPoint) = vbArray + vbDouble)
    
    ' 计算圆心和半径
    Dim centerPoint As Variant, radius As Double
    centerPoint = math.GetMiddlePointBetween2Point(startPoint, endPoint)
    radius = math.GetDistanceBetween2Point(startPoint, endPoint) / 2
    
    Set AddCircleBy2Point = AddCircle(centerPoint, radius)
End Function

' 三点画圆
Public Function AddCircleBy3Point(ByVal startPoint As Variant, ByVal onPoint As Variant, ByVal endPoint As Variant) As AcadCircle
    Debug.Assert (VarType(startPoint) = vbArray + vbDouble)
    Debug.Assert (VarType(onPoint) = vbArray + vbDouble)
    Debug.Assert (VarType(endPoint) = vbArray + vbDouble)
    
    ' 计算圆心
    Dim centerPoint(0 To 2) As Double
    If (Not math.GetCenterBy3Point(startPoint, onPoint, endPoint, centerPoint)) Then
        MsgBox "在AddCircleBy3Point函数中，由于指定的三点共线，创建圆失败！"
        Exit Function
    End If
    
    ' 计算半径
    Dim radius As Double
    radius = math.GetDistanceBetween2Point(centerPoint, startPoint)
    
    Set AddCircleBy3Point = AddCircle(centerPoint, radius)
End Function

' 绘制圆弧
' startAngle: endAngle: 均为弧度值
Public Function AddArc(ByVal centerPoint As Variant, ByVal radius As Double, ByVal startAngle As Double, ByVal endAngle As Double) As AcadArc
    Debug.Assert (VarType(centerPoint) = vbArray + vbDouble)
    Debug.Assert (radius > 0)
    
    Set AddArc = ThisDrawing.ModelSpace.AddArc(centerPoint, radius, startAngle, endAngle)
End Function

Public Function AddArcByCenterStartEndPoint(ByVal centerPoint As Variant, ByVal startPoint As Variant, ByVal endPoint As Variant) As AcadArc
    Debug.Assert (VarType(centerPoint) = vbArray + vbDouble)
    Debug.Assert (VarType(startPoint) = vbArray + vbDouble)
    Debug.Assert (VarType(endPoint) = vbArray + vbDouble)
    
    Dim radius1 As Double, radius2 As Double
    radius1 = math.GetDistanceBetween2Point(centerPoint, startPoint)
    radius2 = math.GetDistanceBetween2Point(centerPoint, endPoint)
    Debug.Assert (Abs(radius1 - radius2) < 0.0000001)
    
    ' 计算起始和终止角度
    Dim startAngle As Double, endAngle As Double
    startAngle = ThisDrawing.Utility.AngleFromXAxis(centerPoint, startPoint)
    endAngle = ThisDrawing.Utility.AngleFromXAxis(centerPoint, endPoint)
    
    Set AddArcByCenterStartEndPoint = AddArc(centerPoint, radius1, startAngle, endAngle)
End Function

Public Function AddArcByCenterStartPointAndArcLength(ByVal centerPoint As Variant, ByVal startPoint As Variant, ByVal arcLength As Double) As AcadArc
    Debug.Assert (VarType(centerPoint) = vbArray + vbDouble)
    Debug.Assert (VarType(startPoint) = vbArray + vbDouble)
    Debug.Assert (arcLength > 0)
    
    Dim radius As Double
    radius = math.GetDistanceBetween2Point(centerPoint, startPoint)
    
    Dim startAngle As Double, endAngle As Double
    startAngle = ThisDrawing.Utility.AngleFromXAxis(centerPoint, startPoint)
    endAngle = arcLength / radius + startAngle
    
    Set AddArcByCenterStartPointAndArcLength = AddArc(centerPoint, radius, startAngle, endAngle)
End Function

' 三点法绘制圆弧
Public Function AddArcBy3Point(ByVal startPoint As Variant, ByVal onPoint As Variant, ByVal endPoint As Variant) As AcadArc
    Debug.Assert (VarType(startPoint) = vbArray + vbDouble)
    Debug.Assert (VarType(onPoint) = vbArray + vbDouble)
    Debug.Assert (VarType(endPoint) = vbArray + vbDouble)
    
    ' 计算圆心
    Dim centerPoint(0 To 2) As Double
    If (Not math.GetCenterBy3Point(startPoint, onPoint, endPoint, centerPoint)) Then
        MsgBox "在AddCircleBy3Point函数中，由于指定的三点共线，创建圆失败！"
        Exit Function
    End If
    
    ' 计算半径
    Dim radius As Double
    radius = math.GetDistanceBetween2Point(centerPoint, startPoint)
    
    ' 计算起始和终止角度
    Dim startAngle As Double, endAngle As Double
    startAngle = ThisDrawing.Utility.AngleFromXAxis(centerPoint, startPoint)
    endAngle = ThisDrawing.Utility.AngleFromXAxis(centerPoint, endPoint)
    
    Set AddArcBy3Point = AddArc(centerPoint, radius, startAngle, endAngle)
End Function

' 2-3
' 多段线基准函数
Public Function AddLWPolyline(ByVal verts As Variant, Optional closed As Boolean = False, Optional width As Double = 0) As AcadLWPolyline
    Debug.Assert (VarType(verts) = vbArray + vbDouble)
    Debug.Assert (UBound(verts) > 2 And UBound(verts) Mod 2 = 1)
    
    Set AddLWPolyline = ThisDrawing.ModelSpace.AddLightWeightPolyline(verts)
    If (closed) Then
        AddLWPolyline.closed = True
    End If
    AddLWPolyline.ConstantWidth = width
End Function

' 创建矩形
Public Function AddRectangle(ByVal point1 As Variant, ByVal point2 As Variant) As AcadLWPolyline
    Dim x(0 To 1) As Double, y(0 To 1) As Double
    SetPoint2d x, point1(0), point2(0)
    SetPoint2d y, point1(1), point2(1)
    
    Dim xMin As Double, xMax As Double, yMin As Double, yMax As Double
    math.MinMaxOfArray x, xMin, xMax
    math.MinMaxOfArray y, yMin, yMax
    
    Dim point(0 To 1) As Double
    SetPoint2d point, xMin, yMin
    Dim pointList As New cls2dPointArray
    pointList.Append point
    SetPoint2d point, xMax, yMin
    pointList.Append point
    SetPoint2d point, xMax, yMax
    pointList.Append point
    SetPoint2d point, xMin, yMax
    pointList.Append point
    
    AddLWPolyline pointList.ToArray(), True
End Function

Public Function AddRectangle1(ByVal point1 As Variant, ByVal point2 As Variant) As AcadLWPolyline
    Dim x(0 To 1) As Double, y(0 To 1) As Double
    SetPoint2d x, point1(0), point2(0)
    SetPoint2d y, point1(1), point2(1)
    
    Dim xMin As Double, xMax As Double, yMin As Double, yMax As Double
    math.MinMaxOfArray x, xMin, xMax
    math.MinMaxOfArray y, yMin, yMax
    
    Dim points(0 To 7) As Double
    points(0) = xMin
    points(1) = yMin
    points(2) = xMax
    points(3) = yMin
    points(4) = xMax
    points(5) = yMax
    points(6) = xMin
    points(7) = yMax
    
    AddLWPolyline points, True
End Function

' 创建多边形
Public Function AddPolygon(ByVal centerPoint As Variant, ByVal sideCount As Integer, ByVal radius As Double, _
    Optional width As Double = 0, Optional angle As Double = 0) As AcadLWPolyline
    ' 计算每条边对应的角度
    Dim sideAngle As Double
    sideAngle = 2 * math.PI() / sideCount
    
    ' 构建顶点数组
    Dim verts As New cls2dPointArray
    Dim i As Integer
    Dim point(0 To 1) As Double
    For i = 0 To 2 * sideCount - 1
        If i Mod 2 = 0 Then
            point(0) = centerPoint(0) + radius * Cos((i \ 2) * sideAngle)
        Else
            point(1) = centerPoint(1) + radius * Sin((i \ 2) * sideAngle)
            verts.Append point
        End If
    Next i
    
    Set AddPolygon = AddLWPolyline(verts.ToArray(), True, width)
    AddPolygon.Rotate centerPoint, angle
    AddPolygon.Update
End Function

' 创建箭头
Public Function AddLeaderByPolyline(ByVal startPoint As Variant, ByVal endPoint As Variant, _
    Optional widthScale As Double = 0.3) As AcadLWPolyline
    Debug.Assert (VarType(startPoint) = vbArray + vbDouble)
    Debug.Assert (VarType(endPoint) = vbArray + vbDouble)
    Debug.Assert (UBound(startPoint) = 1)
    Debug.Assert (UBound(endPoint) = 1)
    
    Dim verts As New cls2dPointArray
    verts.Append startPoint
    verts.Append endPoint
    
    Set AddLeaderByPolyline = AddLWPolyline(verts.ToArray())
    
    Dim length As Double
    length = math.GetDistanceBetween2Point(startPoint, endPoint)
    AddLeaderByPolyline.SetWidth 0, length * widthScale, 0
End Function

' 2-4
' 创建面域
Public Function AddRegion(ByRef ents() As AcadEntity, ByRef regions As Variant, ByRef Count As Integer) As Boolean
    On Error GoTo errHandle
    
    regions = ThisDrawing.ModelSpace.AddRegion(ents)
    Count = UBound(regions) + 1
    AddRegion = True
    
    Exit Function
    
errHandle:
    If Err.number = -2145386493 Then
        Debug.Print "AddRegion函数：面域定义边界未闭合！"
        Count = -1
        AddRegion = False
    End If
    Err.Clear
End Function

' 2-5
' 创建单行文字
Public Function AddText(ByVal textString As String, ByVal insertPoint As Variant, ByVal height As Double) As AcadText
    Debug.Assert (VarType(insertPoint) = vbArray + vbDouble)
    Debug.Assert (UBound(insertPoint) = 2)
    
    Set AddText = ThisDrawing.ModelSpace.AddText(textString, insertPoint, height)
End Function

' 在矩形内部创建大小合适的文字
Public Function AddTextInRectangle(ByVal point1 As Variant, ByVal point2 As Variant, ByVal textString As String, Optional ratio As Double = 0.7) As AcadText
    Debug.Assert (VarType(point1) = vbArray + vbDouble)
    Debug.Assert (UBound(point1) = 2)
    Debug.Assert (VarType(point2) = vbArray + vbDouble)
    Debug.Assert (UBound(point2) = 2)
    
    ' 计算矩形的宽、高和中心点
    Dim rectHeight As Double, rectWidth As Double, centerPoint As Variant
    rectHeight = Abs(point1(1) - point2(1))
    rectWidth = Abs(point1(0) - point2(0))
    centerPoint = math.GetMiddlePointBetween2Point(point1, point2)
    
    ' 创建文字，计算其高宽比
    Dim text As AcadText
    Set text = AddText(textString, centerPoint, rectHeight)
    Dim minPoint As Variant, maxPoint As Variant
    text.GetBoundingBox minPoint, maxPoint
    Dim textHeight As Double, textWidth As Double
    textHeight = Abs(minPoint(1) - maxPoint(1))
    textWidth = Abs(minPoint(0) - maxPoint(0))
        
    ' 根据矩形的宽、高和文字的容纳比例确定文字的高或宽
    Dim heightRatio As Double
    heightRatio = textHeight / textWidth
    If (heightRatio > rectHeight / rectWidth) Then
        textHeight = rectHeight * ratio
    Else
        textWidth = rectWidth * ratio
        textHeight = textWidth * heightRatio
    End If
    
    ' 缩放和移动文字
    text.Alignment = acAlignmentMiddleCenter
    text.TextAlignmentPoint = centerPoint
    text.height = textHeight
    
    Set AddTextInRectangle = text
End Function

' 创建多行文字
Public Function AddMText(ByVal insertPoint As Variant, ByVal width As Double, ByVal textString As String) As AcadMText
    Debug.Assert (VarType(insertPoint) = vbArray + vbDouble)
    Debug.Assert (UBound(insertPoint) = 2)

    Set AddMText = ThisDrawing.ModelSpace.AddMText(insertPoint, width, textString)
End Function

' 2-6
' 图案填充
Public Function AddHatch(ByRef ents() As AcadEntity, ByVal patternType As AcPatternType, ByVal patternName As String, ByVal associativity As Boolean) As AcadHatch
    On Error GoTo ERR_HANDLE
    
    ' 创建填充对象
    Dim hatch As AcadHatch
    Set hatch = ThisDrawing.ModelSpace.AddHatch(patternType, patternName, associativity, acHatchObject)
    
    ' 添加填充外边界
    hatch.AppendOuterLoop ents
    hatch.Evaluate
    ThisDrawing.Regen True
    
    Set AddHatch = hatch
    Exit Function
    
ERR_HANDLE:
    If Err.number = -2145386493 Then
        Debug.Print "AddRegion函数：填充定义边界未闭合！"
    End If
    Err.Clear
End Function

' 渐变真彩色填充
Public Function AddGradientHatch(ByRef ents() As AcadEntity, ByVal patternType As AcGradientPatternType, ByVal patternName As String, ByVal associativity As Boolean, _
    ByVal color1 As AcadAcCmColor, ByVal color2 As AcadAcCmColor) As AcadHatch
    On Error GoTo ERR_HANDLE
    
    ' 创建填充对象
    Dim hatch As AcadHatch
    Set hatch = ThisDrawing.ModelSpace.AddHatch(patternType, patternName, associativity, acGradientObject)
    
    hatch.GradientColor1 = color1
    hatch.GradientColor2 = color2
    
    ' 添加填充外边界
    hatch.AppendOuterLoop ents
    hatch.Evaluate
    ThisDrawing.Regen True
    
    Set AddGradientHatch = hatch
    Exit Function
    
ERR_HANDLE:
    If Err.number = -2145386493 Then
        Debug.Print "AddRegion函数：填充定义边界未闭合！"
    End If
    Err.Clear
End Function

' 真彩色填充
Public Function AddTrueColorHatch(ByRef ents() As AcadEntity, ByVal associativity As Boolean, ByVal color As AcadAcCmColor) As AcadHatch
    On Error GoTo ERR_HANDLE
    
    ' 创建填充对象
    Dim hatch As AcadHatch
    Set hatch = ThisDrawing.ModelSpace.AddHatch(acPreDefinedGradient, "LINEAR", associativity, acGradientObject)
    
    hatch.GradientColor1 = color
    hatch.GradientColor2 = color
    
    ' 添加填充外边界
    hatch.AppendOuterLoop ents
    hatch.Evaluate
    ThisDrawing.Regen True
    
    Set AddTrueColorHatch = hatch
    Exit Function
    
ERR_HANDLE:
    If Err.number = -2145386493 Then
        Debug.Print "AddRegion函数：填充定义边界未闭合！"
    End If
    Err.Clear
End Function

' 2-7
' 对齐标注
Public Function AddDimAligned(ByVal extLine1Point As Variant, ByVal extLine2Point As Variant, ByVal textPosition As Variant, _
    Optional text As String = "", Optional xOffset As Double = 0, Optional yOffset As Double = 0) As AcadDimAligned
    Dim objDim As AcadDimAligned
    Set objDim = ThisDrawing.ModelSpace.AddDimAligned(extLine1Point, extLine2Point, textPosition)
    
    ' 指定新的标注文字内容
    If Len(text) > 0 Then
        objDim.TextOverride = text
    End If
    
    ' 移动文字位置前，需先指定尺寸线的变化方式（这里指定为：尺寸线不动，在文字和尺寸线之间加箭头）
    If Abs(xOffset) > 0 Or Abs(yOffset) > 0 Then
        objDim.TextMovement = acMoveTextAddLeader
        SetPoint3d textPosition, textPosition(0) + xOffset, textPosition(1) + yOffset, textPosition(2)
        objDim.textPosition = textPosition
    End If
    
    objDim.Update

    Set AddDimAligned = objDim
End Function

' 转角标注
Public Function AddDimRotated(ByVal extLine1Point As Variant, ByVal extLine2Point As Variant, ByVal dimLineLocation As Variant, _
    ByVal rotationAngle As Double, Optional text As String = "") As AcadDimRotated
    Dim objDim As AcadDimRotated
    Set objDim = ThisDrawing.ModelSpace.AddDimRotated(extLine1Point, extLine2Point, dimLineLocation, rotationAngle)
    
    If Len(text) > 0 Then
        objDim.TextOverride = text
    End If
    
    Set AddDimRotated = objDim
End Function

' 根据圆心、角度(弧度)和半径来标注半径
Public Function AddDimRadial(ByVal centerPoint As Variant, ByVal radius As Double, ByVal angle As Double, Optional leaderLength As Double = 5) As AcadDimRadial
    Dim chordPoint As Variant
    chordPoint = ThisDrawing.Utility.PolarPoint(centerPoint, angle, radius)
    
    Set AddDimRadial = ThisDrawing.ModelSpace.AddDimRadial(centerPoint, chordPoint, leaderLength)
End Function

' 根据圆心、角度(弧度)和半径来标注直径
Public Function AddDimDiametric(ByVal centerPoint As Variant, ByVal radius As Double, ByVal angle As Double, Optional leaderLength As Double = 5) As AcadDimDiametric
    Dim chordPoint As Variant, farChordPoint As Variant
    chordPoint = ThisDrawing.Utility.PolarPoint(centerPoint, angle, radius)
    farChordPoint = ThisDrawing.Utility.PolarPoint(centerPoint, angle + math.PI(), radius)
    
    Set AddDimDiametric = ThisDrawing.ModelSpace.AddDimDiametric(chordPoint, farChordPoint, leaderLength)
End Function

' 角度标注
Public Function AddDimAngular(ByVal vertexPoint As Variant, ByVal startPoint As Variant, ByVal endPoint As Variant, _
    ByVal textPoint As Variant, Optional bArcDim As Boolean = True) As AcadDimAngular
    If bArcDim Then
        Set AddDimAngular = ThisDrawing.ModelSpace.AddDimAngular(vertexPoint, startPoint, endPoint, textPoint)
    Else
        Set AddDimAngular = ThisDrawing.ModelSpace.AddDim3PointAngular(vertexPoint, startPoint, endPoint, textPoint)
    End If
End Function

' 坐标标注
Public Function AddDimOrdinate(ByVal dimPoint As Variant, ByVal xOffset As Double, ByVal yOffset As Double)
    ' 两个文字位置定义点
    Dim xTextPoint(0 To 2) As Double
    Dim yTextPoint(0 To 2) As Double
    
    SetPoint3d xTextPoint, dimPoint(0), dimPoint(1) + yOffset, 0
    SetPoint3d yTextPoint, dimPoint(0) + xOffset, dimPoint(1), 0
    
    ThisDrawing.ModelSpace.AddDimOrdinate dimPoint, xTextPoint, True
    ThisDrawing.ModelSpace.AddDimOrdinate dimPoint, yTextPoint, False
End Function

' 2-8
' 获得文字字符串的宽度
Public Function GetTextStringWidth(ByVal text As String) As Double
    ' 创建文字对象
    Dim insertPoint(0 To 2) As Double
    SetPoint3d insertPoint, 0, 0, 0
    Dim textObj As AcadText
    Set textObj = AddText(text, insertPoint, height)
    
    ' 获得文字的宽度
    Dim minPoint As Variant, maxPoint As Variant
    textObj.GetBoundingBox minPoint, maxPoint
    GetTextStringWidth = maxPoint(0) - minPoint(0)
    
    textObj.Delete
End Function

' 创建引线和注释
Public Function AddLeader(ByVal points As Variant, ByVal text As String, ByVal height As Double, _
    ByVal location As TextLocation, Optional offset As Double = 0) As AcadLeader
    Debug.Assert (VarType(points) = vbArray + vbDouble)
    Debug.Assert (UBound(points) Mod 3 = 2)
    
    ' 创建多行文字对象
    Dim insertPoint(0 To 2) As Double
    SetPoint3d insertPoint, 0, 0, 0
    Dim mtext As AcadMText
    Set mtext = AddMText(insertPoint, GetTextStringWidth(text), text)
    
    ' 修改文字的位置
    Dim number As Integer
    number = UBound(points)
    Select Case location
        Case TextTop
            SetPoint3d insertPoint, points(number - 2) - offset, points(number - 1) + offset, points(number)
            mtext.AttachmentPoint = acAttachmentPointBottomRight
            mtext.insertionPoint = insertPoint
        Case TextBottom
            SetPoint3d insertPoint, points(number - 2) - offset, points(number - 1) - offset, points(number)
            mtext.AttachmentPoint = acAttachmentPointTopRight
            mtext.insertionPoint = insertPoint
        Case TextLeft
            SetPoint3d insertPoint, points(number - 2) - offset, points(number - 1), points(number)
            mtext.AttachmentPoint = acAttachmentPointMiddleRight
            mtext.insertionPoint = insertPoint
        Case TextRight
            SetPoint3d insertPoint, points(number - 2) + offset, points(number - 1), points(number)
            mtext.AttachmentPoint = acAttachmentPointMiddleLeft
            mtext.insertionPoint = insertPoint
    End Select
    
    ' 创建引线对象
    If location = TextLeft Or location = TextRight Then
        Set AddLeader = ThisDrawing.ModelSpace.AddLeader(points, mtext, acLineWithArrow)
        AddLeader.VerticalTextPosition = acVertCentered
    Else
        Set AddLeader = ThisDrawing.ModelSpace.AddLeader(points, Nothing, acLineWithArrow)
    End If
End Function

' 2-9
' 根据外界矩形创建椭圆
Public Function AddEllipse(ByVal pt1 As Variant, ByVal pt2 As Variant) As AcadEllipse
    Dim majAxisLen As Double, minAxisLen As Double     ' 长轴和短轴的长度
    Dim ptCen As Variant        ' 中心点
    Dim radRatio As Double      ' 长、短轴比例
    Dim ptmajAxis(0 To 2) As Double         ' 长轴的端点
    
    ' 计算长轴和短轴的长度以及半径比例
    majAxisLen = Abs(pt1(0) - pt2(0))
    minAxisLen = Abs(pt1(1) - pt2(1))
    radRatio = minAxisLen / majAxisLen
    
    ' 根据长轴所在的坐标轴调整数据
    If radRatio <= 1 Then
        SetPoint3d ptmajAxis, majAxisLen / 2, 0, 0
    ElseIf radRatio > 1 Then
        SetPoint3d ptmajAxis, 0, minAxisLen / 2, 0
        radRatio = 1 / radRatio
    End If
    
    Dim math As New clsMath
    ptCen = math.GetMiddlePointBetween2Point(pt1, pt2)
    Set AddEllipse = ThisDrawing.ModelSpace.AddEllipse(ptCen, ptmajAxis, radRatio)
End Function

' 创建样条曲线
Public Function AddSpline(ByVal points As Variant, Optional startTangent As Variant = Empty, Optional endTangent As Variant = Empty) As AcadSpline
    Debug.Assert (VarType(points) = vbArray + vbDouble)
    Debug.Assert (UBound(points) > 4 And UBound(points) Mod 3 = 2)
    If startTangent <> Empty Then
        Debug.Assert (VarType(startTangent) = vbArray + vbDouble)
        Debug.Assert (UBound(startTangent) = 2)
    End If
    If endTangent <> Empty Then
        Debug.Assert (VarType(endTangent) = vbArray + vbDouble)
        Debug.Assert (UBound(endTangent) = 2)
    End If
    
    Dim vec(0 To 2) As Double
    If startTangent = Empty Then
        startTangent = vec
        SetPoint3d startTangent, points(3) - points(0), points(4) - points(1), points(5) - points(2)
    End If
    If endTangent = Empty Then
        Dim size As Integer
        size = UBound(points)
        endTangent = vec
        SetPoint3d endTangent, points(size - 2) - points(size - 5), points(size - 1) - points(size - 4), points(size) - points(size - 3)
    End If
    
    Set AddSpline = ThisDrawing.ModelSpace.AddSpline(points, startTangent, endTangent)
End Function

' 2-10
' 获得一条直线或圆的起终点和凸度
Private Function GetStartEndPointAndBulge(ByVal ent As AcadEntity, ByVal bReverseBulge As Boolean, _
    ByRef startPoint As Variant, ByRef endPoint As Variant, ByRef bulge As Double) As Boolean
    If TypeOf ent Is AcadLine Then
        Dim line As AcadLine
        Set line = ent
        startPoint = line.startPoint
        endPoint = line.endPoint
        bulge = 0
        
        GetStartEndPointAndBulge = True
    ElseIf TypeOf ent Is AcadArc Then
        Dim arc As AcadArc
        Set arc = ent
        startPoint = arc.startPoint
        endPoint = arc.endPoint
        If (bReverseBulge) Then
            bulge = Tan(-arc.TotalAngle / 4)
        Else
            bulge = Tan(arc.TotalAngle / 4)
        End If
        
        GetStartEndPointAndBulge = True
    Else
        GetStartEndPointAndBulge = False
    End If
End Function

' 交换多段线的第一个和最后一个顶点
Private Function SwapFirstLastVert(ByVal poly As AcadLWPolyline)
    Dim points As Variant
    points = poly.Coordinates
    
    Dim a As Double
    a = points(0)
    points(0) = points(UBound(points) - 1)
    points(UBound(points) - 1) = a
    a = points(1)
    points(1) = points(UBound(points))
    points(UBound(points)) = a
    
    poly.Coordinates = points
End Function

' 根据多条首尾相连的线创建闭合多段线
Public Function AddLWPolylineByEnts(ByRef ents() As AcadEntity, ByRef poly As AcadLWPolyline) As Boolean
    ' 用一个动态数组来保存边界对象
    Dim entArray As New clsEntityArray
    Dim i As Integer
    For i = 0 To UBound(ents)
        entArray.Append ents(i)
    Next i
    
    ' 根据第一个实体创建多段线
    Dim verts As New cls2dPointArray
    Dim startPoint As Variant, endPoint As Variant, bulge As Double
    Dim revFirstBulge As Double
    If (GetStartEndPointAndBulge(ents(0), False, startPoint, endPoint, bulge)) Then
        verts.Append startPoint
        verts.Append endPoint
        'Set poly = mSpace.AddLWPolyline(verts.ToArray())
        Set poly = AddLWPolyline(verts.ToArray())
        
        poly.SetBulge 0, bulge
        
        ' 保存第一个实体的反向凸度备用
        GetStartEndPointAndBulge ents(0), True, startPoint, endPoint, revFirstBulge
    Else
        AddLWPolylineByEnts = False
        Exit Function
    End If
    
    entArray.RemoveAt 0
    
    ' 从一个实体开始，不断添加多段线的顶点
    Dim vertCount As Integer        ' 多段线顶点的个数
    vertCount = 2
    Dim previousPoint As Variant
    previousPoint = endPoint
    Dim firstStartPoint As Variant      ' 第一个实体的起点
    firstStartPoint = startPoint
    Dim math As New clsMath
    Dim bExit As Boolean
    bExit = False
    
ARRAYLOOP:
    For i = 0 To entArray.GetCount - 1
        Dim ent As AcadEntity
        entArray.GetAt i, ent
        
        ' 判断当前实体的起点或终点是否和上一个顶点重合
        If (GetStartEndPointAndBulge(ent, False, startPoint, endPoint, bulge)) Then
            If (math.PointIsEqual(previousPoint, startPoint)) Then
                poly.AddVertex vertCount, math.Point3dto2d(endPoint)
                poly.SetBulge vertCount - 1, bulge
                previousPoint = endPoint
                
                vertCount = vertCount + 1
                entArray.RemoveAt i
                GoTo ARRAYLOOP
            ElseIf (math.PointIsEqual(previousPoint, endPoint)) Then
                GetStartEndPointAndBulge ent, True, startPoint, endPoint, bulge
                poly.AddVertex vertCount, math.Point3dto2d(startPoint)
                poly.SetBulge vertCount - 1, bulge
                previousPoint = startPoint
                
                vertCount = vertCount + 1
                entArray.RemoveAt i
                GoTo ARRAYLOOP
            Else
                If i = entArray.GetCount() - 1 Then
                    If bExit Then
                        Exit For
                    End If
                End If
                
                If (Not bExit) And vertCount = 2 Then
                    previousPoint = firstStartPoint
                    
                    ' 如果第二个实体未找到和第一个实体的重合点，应交换多段线的两个顶点
                    SwapFirstLastVert poly
                    ' 并且修改第一段曲线的凸度
                    poly.SetBulge 0, revFirstBulge
                    
                    bExit = True
                    
                    GoTo ARRAYLOOP
                End If
            End If
            
        End If
    Next i
    
    If i = 0 Then
        AddLWPolylineByEnts = True
    Else
        poly.Delete
        AddLWPolylineByEnts = False
    End If
End Function

'
'
'
'

'
'

'
''

'
'
'
'


'
'
'

'
'
'
'

'

Attribute VB_Name = "clsPolyUtility"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' 获得多段线的顶点个数
Public Function GetVertexCount(ByVal poly As AcadEntity) As Integer
    If TypeOf poly Is AcadLWPolyline Then
        GetVertexCount = (UBound(poly.Coordinates) + 1) / 2
    ElseIf TypeOf poly Is AcadPolyline Then
        GetVertexCount = (UBound(poly.Coordinates) + 1) / 3
    End If
End Function

Attribute VB_Name = "clsSelectionSet"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_sset As AcadSelectionSet      ' 选择集对象
Private m_name As String                ' 选择集的名称
Private m_fType() As Integer            ' 过滤器规则
Private m_fData() As Variant            ' 过滤器参数
Private m_bEnableFilter As Boolean      ' 是否启动过滤器
Private m_bHasFilter As Boolean         ' 是否有过滤器可用

' 创建选择集
Public Sub Create(ByVal name As String)
    Debug.Assert (m_sset Is Nothing)
    On Error Resume Next
    
    If Not IsNull(ThisDrawing.SelectionSets.Item(name)) Then
        Set m_sset = ThisDrawing.SelectionSets.Item(name)
        m_sset.Delete
    End If
    Set m_sset = ThisDrawing.SelectionSets.Add(name)
    m_name = name
End Sub

' 删除选择集
Public Sub Delete()
    Debug.Assert (Not m_sset Is Nothing)
    
    m_sset.Delete
    Set m_sset = Nothing
End Sub

' 添加一个实体
Public Sub AddEntity(ByVal ent As AcadEntity)
    Debug.Assert (Not m_sset Is Nothing)
    
    Dim objCollection(0) As AcadEntity
    Set objCollection(0) = ent
    
    m_sset.AddItems objCollection
End Sub

' 添加多个实体
Public Function AddEntitys(ByVal ents As Variant) As Boolean
    Debug.Assert (Not m_sset Is Nothing)
    
    If VarType(ents) <> vbArray + vbObject Then
        AddEntitys = False
        Exit Function
    End If
    
    Dim objCollection() As AcadEntity
    ReDim objCollection(UBound(ents))
    
    Dim i As Integer
    For i = 0 To UBound(ents)
        Set objCollection(i) = ents(i)
    Next i
    
    m_sset.AddItems objCollection
    AddEntitys = True
End Function

' 删除一个实体
Public Sub RemoveEntity(ByVal ent As AcadEntity)
    Debug.Assert (Not m_sset Is Nothing)

    Dim objCollection(0) As AcadEntity
    Set objCollection(0) = ent
    
    m_sset.RemoveItems objCollection
End Sub

' 删除多个实体
Public Function RemoveEntitys(ByVal ents As Variant) As Boolean
    Debug.Assert (Not m_sset Is Nothing)

    If VarType(ents) <> vbArray + vbObject Then
        RemoveEntitys = False
        Exit Function
    End If
    
    Dim objCollection() As AcadEntity
    ReDim objCollection(UBound(ents))
    
    Dim i As Integer
    For i = 0 To UBound(ents)
        Set objCollection(i) = ents(i)
    Next i
    
    m_sset.RemoveItems objCollection
    RemoveEntitys = True
End Function

' 导出为对象数组
Public Function ExportToEntArray() As Variant
    Debug.Assert (Not m_sset Is Nothing)
    
    Dim objCollection() As AcadEntity
    ReDim objCollection(SSet.Count - 1)
    
    Dim i As Integer
    For i = 0 To SSet.Count - 1
        Set objCollection(i) = SSet.Item(i)
    Next i
    
    ExportToEntArray = objCollection
End Function

' 点选对象
Public Sub SelectAtPoint(ByVal point As Variant)
    Debug.Assert (VarType(point) = vbArray + vbDouble)
    Debug.Assert (UBound(point) = 2)
    Debug.Assert (Not m_sset Is Nothing)
    
    If m_bHasFilter And m_bEnableFilter Then
        m_sset.Select acSelectionSetCrossing, point, point, m_fType, m_fData
    Else
        m_sset.Select acSelectionSetCrossing, point, point
    End If
End Sub

' 多边形选择
Public Sub SelectByPolyon(ByVal poly As AcadLWPolyline, ByVal mode As AcSelect)
    Debug.Assert (Not m_sset Is Nothing)
    
    ' 将轻量多段线的坐标输入到点数组中
    Dim pointArrs() As Double
    ReDim pointArrs((UBound(poly.Coordinates) + 1) * 3 / 2 - 1)
    
    Dim i As Integer
    For i = 0 To ((UBound(poly.Coordinates) + 1) / 2 - 1)
        pointArrs(3 * i) = poly.Coordinates(2 * i)
        pointArrs(3 * i + 1) = poly.Coordinates(2 * i + 1)
        pointArrs(3 * i + 2) = 0
    Next i
    
    If m_bHasFilter And m_bEnableFilter Then
        m_sset.SelectByPolygon mode, pointArrs, m_fType, m_fData
    Else
        m_sset.SelectByPolygon mode, pointArrs
    End If
End Sub

' 在屏幕上选择实体
Public Sub SelectOnScreen()
    Debug.Assert (Not m_sset Is Nothing)
    
    If m_bHasFilter And m_bEnableFilter Then
        m_sset.SelectOnScreen m_fType, m_fData
    Else
        m_sset.SelectOnScreen
    End If
End Sub

' 其他选择方式
Public Sub SelectEntity(ByVal mode As AcSelect, Optional point1 As Variant = Empty, Optional point2 As Variant = Empty)
    Debug.Assert (Not m_sset Is Nothing)
    
    If m_bHasFilter And m_bEnableFilter Then
        m_sset.Select mode, point1, point2, m_fType, m_fData
    Else
        m_sset.Select mode, point1, point2
    End If
End Sub

' 创建选择过滤器
Public Sub SetFilter(ParamArray filter())
    Debug.Assert (UBound(filter) Mod 2 = 1)
    
    Dim Count As Integer
    Count = (UBound(filter) + 1) / 2
    ReDim m_fType(Count - 1)
    ReDim m_fData(Count - 1)
    m_bHasFilter = True
    
    Dim i As Integer
    For i = 0 To Count - 1
        m_fType(i) = filter(2 * i)
        m_fData(i) = filter(2 * i + 1)
    Next i
End Sub

' 是否启用选择过滤器
Public Sub EnableFilter(Optional bEnable As Boolean = True)
    m_bEnableFilter = bEnable
End Sub

' 获得选择集中的实体个数
Public Function Count() As Integer
    Debug.Assert (Not m_sset Is Nothing)

    Count = m_sset.Count
End Function

' 获得选择集中的实体集合
Public Function GetAcadSelectionSet() As AcadSelectionSet
    Debug.Assert (Not m_sset Is Nothing)

    Set GetAcadSelectionSet = m_sset
End Function

Private Sub Class_Initialize()
    Set m_sset = Nothing
    m_bHasFilter = False
    m_bEnableFilter = False
End Sub

Private Sub Class_Terminate()
    If Not m_sset Is Nothing Then
        m_sset.Delete
        Set m_sset = Nothing
    End If
End Sub

Attribute VB_Name = "frmMain"
Attribute VB_Base = "0{48B90003-834B-4330-96D6-D15EF5F82B1B}{A679C2A3-6B20-413E-A58E-07BD1EA6BAFA}"
Attribute VB_GlobalNameSpace = False
Attribute VB_Creatable = False
Attribute VB_PredeclaredId = True
Attribute VB_Exposed = False
Attribute VB_TemplateDerived = False
Attribute VB_Customizable = False
Option Explicit

Private Sub cmdColor_Click()
    On Error Resume Next
    
    With comDlg
        .DialogTitle = "选择文字颜色"
        .ShowColor
    End With
    
    txtFile.ForeColor = comDlg.color
End Sub

Private Sub cmdExit_Click()
    Unload Me
End Sub

Private Sub cmdFont_Click()
    On Error Resume Next
    
    With comDlg
        .flags = cdlCFBoth + cdlCFEffects
        .ShowFont
    End With
    
    txtFile.Font = comDlg.FONTNAME
End Sub

Private Sub cmdOpen_Click()
    '错误处理
    On Error Resume Next
    
    '设置标准对话框
    With comDlg
        .DialogTitle = "选择文本文件"
        .filter = "文本文件(*.txt)|*.txt|所有文件(*.*)|*.*"
        .InitDir = "C:\"
        .ShowOpen
    End With
    
    '文件类型错误的判断
    If Right(comDlg.fileName, 3) <> "txt" Then
        MsgBox "不支持的文件格式！", vbCritical, "警告"
        Exit Sub
    End If
    
    '打开文件的操作
    Open comDlg.fileName For Input As #1
    txtFile.text = StrConv(InputB$(LOF(1), 1), vbUnicode)
    Close #1
End Sub

Private Sub cmdSave_Click()
    '错误处理
    On Error Resume Next
    
    '设置标准对话框
    With comDlg
        .DialogTitle = "保存文本文件"
        .filter = "文本文件(*.txt)|*.txt|所有文件(*.*)|*.*"
        .InitDir = "C:\"
        .DefaultExt = "txt"
        .ShowSave
    End With
    
    '保存文件的操作
    Open comDlg.fileName For Output As #1
    Print #1, txtFile.text
    Close 1

End Sub

Attribute VB_Name = "mdlUtility"
Option Explicit

' 2-1
' 设置三维点的坐标值
Public Function SetPoint3d(ByRef point As Variant, ByVal x As Double, ByVal y As Double, ByVal z As Double)
    Debug.Assert (VarType(point) = vbArray + vbDouble)
    Debug.Assert (LBound(point) = 0 And UBound(point) = 2)

    point(0) = x
    point(1) = y
    point(2) = z
End Function

' 2-3
' 设置二维点坐标值（为包括两个元素的一维数组赋值）
Public Function SetPoint2d(ByRef point As Variant, ByVal x As Double, ByVal y As Double)
    Debug.Assert (VarType(point) = vbArray + vbDouble)
    Debug.Assert (LBound(point) = 0 And UBound(point) = 1)
    
    point(0) = x
    point(1) = y
End Function

' 2-7
' 获得三维点的偏移结果
Public Function OffsetPoint(ByVal point As Variant, ByVal deltaX As Double, ByVal deltaY As Double, Optional deltaZ As Double = 0) As Variant
    Debug.Assert (VarType(point) = vbArray + vbDouble)
    Debug.Assert (LBound(point) = 0 And UBound(point) = 2)
    
    Dim retPoint(0 To 2) As Double
    SetPoint3d retPoint, point(0) + deltaX, point(1) + deltaY, point(2) + deltaZ
    OffsetPoint = retPoint
End Function
