Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit

Public Sub HelloVba()
    Dim strName As String
    strName = InputBox("输入你的名字", "HelloVBA", "My Friend")
    MsgBox strName & ", 让我们在图形窗口中欢迎你!"

    Dim text As AcadText
    Dim insertPoint(0 To 2) As Double
    insertPoint(0) = 10
    insertPoint(1) = 10
    insertPoint(2) = 0
    
    Set text = ThisDrawing.ModelSpace.AddText("Hello, VBA!", insertPoint, 5)
    
    ThisDrawing.Application.ZoomExtents
End Sub
